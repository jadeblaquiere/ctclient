--BSD 3-Clause License
--
--Copyright (c) 2018, jadeblaquiere
--All rights reserved.
--
--Redistribution and use in source and binary forms, with or without
--modification, are permitted provided that the following conditions are met:
--
--* Redistributions of source code must retain the above copyright notice, this
--  list of conditions and the following disclaimer.
--
--* Redistributions in binary form must reproduce the above copyright notice,
--  this list of conditions and the following disclaimer in the documentation
--  and/or other materials provided with the distribution.
--
--* Neither the name of the copyright holder nor the names of its
--  contributors may be used to endorse or promote products derived from
--  this software without specific prior written permission.
--
--THIS SOFTWARE IS PROVIDED BY THE COPYRIGHT HOLDERS AND CONTRIBUTORS "AS IS"
--AND ANY EXPRESS OR IMPLIED WARRANTIES, INCLUDING, BUT NOT LIMITED TO, THE
--IMPLIED WARRANTIES OF MERCHANTABILITY AND FITNESS FOR A PARTICULAR PURPOSE ARE
--DISCLAIMED. IN NO EVENT SHALL THE COPYRIGHT HOLDER OR CONTRIBUTORS BE LIABLE
--FOR ANY DIRECT, INDIRECT, INCIDENTAL, SPECIAL, EXEMPLARY, OR CONSEQUENTIAL
--DAMAGES (INCLUDING, BUT NOT LIMITED TO, PROCUREMENT OF SUBSTITUTE GOODS OR
--SERVICES; LOSS OF USE, DATA, OR PROFITS; OR BUSINESS INTERRUPTION) HOWEVER
--CAUSED AND ON ANY THEORY OF LIABILITY, WHETHER IN CONTRACT, STRICT LIABILITY,
--OR TORT (INCLUDING NEGLIGENCE OR OTHERWISE) ARISING IN ANY WAY OUT OF THE USE
--OF THIS SOFTWARE, EVEN IF ADVISED OF THE POSSIBILITY OF SUCH DAMAGE.

Ciphrtxt DEFINITIONS EXPLICIT TAGS ::=

BEGIN

CTSecretKey ::= SEQUENCE {
    version     INTEGER,
    addr_sec    OCTET STRING,
    enc_sec     OCTET STRING,
    sign_sec    OCTET STRING,
    chk_sec     OCTET STRING,
    t0          INTEGER,
    tStep       INTEGER
}

CTPublicKey ::= SEQUENCE {
    version     INTEGER,
    addr_pub    OCTET STRING,
    enc_pub     OCTET STRING,
    sign_pub    OCTET STRING,
    chk_pub     OCTET STRING,
    t0          INTEGER,
    tStep       INTEGER
}

CTNAKSecretKey ::= SEQUENCE {
    version     INTEGER,
    secret_key  OCTET STRING,
    not_before  INTEGER,
    not_after   INTEGER
}

CTNAKPublicKey ::= SEQUENCE {
    version     INTEGER,
    public_key  OCTET STRING,
    not_before  INTEGER,
    not_after   INTEGER
}

CTNAKAuthChallenge ::= SEQUENCE {
    version     INTEGER,
    challenge   SEQUENCE OF EGCiphertextWPublicKey,
    session_pk  OCTET STRING,
    expire      INTEGER
}

EGCiphertextWPublicKey ::= SEQUENCE {
    public_key  OCTET STRING,
    ctxt        ELGamalCiphertext
}

CTNAKAuthResponse ::= SEQUENCE {
    version     INTEGER,
    session_pk  OCTET STRING,
    ctxt        ELGamalCiphertext
}

ELGamalCiphertext ::= SEQUENCE {
    c           OCTET STRING,
    d           OCTET STRING
}

END
